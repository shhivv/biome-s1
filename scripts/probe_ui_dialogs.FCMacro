# Dump the widgets of every feature task dialog (objectName, class, value, options); run in the GUI.
# Launched by scripts/probe_ui_dialogs.py under the watchdog. Env: S1_REPO, S1_OUT.
import os, sys, json, traceback
sys.path.insert(0, os.environ["S1_REPO"])
from freecad_s1.ui.launch import self_guard
self_guard()
res = {}
try:
    import FreeCADGui as Gui
    from PySide import QtWidgets
    from freecad_s1.goals import StartSpec
    from freecad_s1.runtime.gui_session import GuiSession
    from freecad_s1.schema import Goal, GoalFeature as F
    from freecad_s1.ui.session import ModalGuard, UiSession, wait_until

    BOX = F("base_box", {"w": 40, "d": 30, "h": 12})
    SETUPS = {
        "PartDesign_Pad": [BOX],
        "PartDesign_Revolution": [F("base_ring", {"ri": 10, "ro": 20, "h": 8})],
        "PartDesign_Pocket": [BOX, F("pocket_rect", {"w": 6, "d": 5, "x": 5, "y": 3, "depth": 3})],
        "PartDesign_Hole": [BOX, F("hole_std", {"r": 3, "x": 5, "y": 3})],
        "PartDesign_PolarPattern": [F("base_cyl", {"r": 30, "h": 10}), F("hole", {"r": 3, "x": 12, "y": 0}), F("polar_pattern", {"n": 6})],
        "PartDesign_LinearPattern": [BOX, F("hole", {"r": 2, "x": -10, "y": 0}), F("linear_pattern", {"n": 3, "length": 15})],
        "PartDesign_Mirrored": [BOX, F("hole", {"r": 2, "x": 10, "y": 0}), F("mirror", {})],
        "PartDesign_Fillet": [BOX, F("fillet_top", {"r": 1.5})],
        "PartDesign_Chamfer": [BOX, F("chamfer_top", {"size": 0.8})],
        "PartDesign_Thickness": [BOX, F("shell", {"t": 1.5})],
    }
    s = UiSession()
    for cmd, feats in SETUPS.items():
        s.reset(Goal(feats, level=3, scale=40), StartSpec())
        for _ in range(80):  # teacher steps up to the command, which is then triggered raw (no field checks)
            a = s.expert()[0]
            if a == "cmd:" + cmd:
                break
            s.step(a)
        s.settle()
        action = Gui.Command.get(cmd).getAction()[0]
        wait_until(action.isEnabled, 2.0)
        with ModalGuard(s.messages):
            action.trigger()
            wait_until(lambda: bool(Gui.Control.activeDialog()), 2.0)
        root = s.task_view()
        rows = []
        for w in (root.findChildren(QtWidgets.QWidget) if root else []):
            cn = w.metaObject().className()
            if not w.isVisibleTo(root) or w.objectName() == "qt_spinbox_lineedit" or "Private" in cn:
                continue
            if not any(k in cn for k in ("SpinBox", "ComboBox", "CheckBox", "Button", "LineEdit", "ListWidget")):
                continue
            d = {"cls": cn, "name": w.objectName(), "enabled": w.isEnabled()}
            for attr in ("text", "currentText"):
                if hasattr(w, attr):
                    try:
                        d[attr] = str(getattr(w, attr)())
                    except Exception:
                        pass
            if hasattr(w, "isChecked") and "CheckBox" in cn:
                d["checked"] = bool(w.isChecked())
            if "ComboBox" in cn:
                d["items"] = [w.itemText(i) for i in range(w.count())]
            rows.append(d)
        res[cmd] = rows
        s._close_dialog()
    s.shutdown()
except Exception:
    res["fatal"] = traceback.format_exc()
open(os.environ["S1_OUT"], "w").write(json.dumps(res, indent=1))
os._exit(0)
